package <DD_BROWNFIELD> DeliveryDroneSystemBrownfieldArchitecture {
    doc
    /* 
     * SYSMOD Example Model: Delivery Drone
     *
     * Definition of the Delivery Drone Brownfield Architecture
     *
     * based on SYSMOD v5.1.8
     *
     * Licensed under the Apache License, Version 2.0 (the "License");
     * you may not use this file except in compliance with the License.
     * You may obtain a copy of the License at
     *
     * http://www.apache.org/licenses/LICENSE-2.0
     *
     * Unless required by applicable law or agreed to in writing, software
     * distributed under the License is distributed on an "AS IS" BASIS,
     * WITHOUT WARRANTIES OR CONDITIONS OF ANY KIND, either express or implied.
     * See the License for the specific language governing permissions and
     * limitations under the License.
     *
     * Copyright 2026, MBSE4U, Tim Weilkiens
     */

    private import SYSMOD::*;

    #systemContext part def DeliveryDroneSystemContext {
        doc
        /* The black box brownfield context: the delivery drone system as it exists at
         * the start of the project, together with the actors that already interact
         * with it. It constrains the set of possible solutions. */
        #system part deliveryDroneSystem : DeliveryDroneSystem :>> soi {
            doc
            /* The existing delivery drone system as a black box. */
        }
        #user part operator :> actors {
            doc
            /* The human operator who monitors and commands the system. */
            port controlPort[1] :>> actorPorts;
        }
        #user part customer :> actors {
            doc /* The human customer who hands over or retrieves the package. */
            port packagePort[1] :>> actorPorts;
        }
        #externalSystem part landingZone :> actors {
            doc
            /* A marked landing zone where drones pick up and drop off packages. */
            port dronePort :>> actorPorts;
        }
        #externalSystem part energySupply :> actors {
            doc
            /* The energy supply system that provides electrical energy to the delivery drone system. */
            port energyPort[1] :>> actorPorts;
        }
        #environmentalEffect part environment :> actors {
            doc
            /* Environmental conditions acting on the system, e.g., wind and rain. */
            port conditionsPort :>> actorPorts;
        }
        interface operatorInterface :> asis connect operator.controlPort to deliveryDroneSystem.operatorPort {
            doc
            /* Command and monitoring interface between the operator and the system. */
        }
        interface landingZoneInterface :> asis connect landingZone.dronePort to deliveryDroneSystem.landingZonePort {
            doc
            /* Physical pick-up and drop-off interface at the landing zone. */
        }
        interface environmentInterface :> asis connect environment.conditionsPort to deliveryDroneSystem.environmentPort {
            doc
            /* Exposure of the system to the environmental conditions. */
        }
        interface customerInterface :> asis connect customer.packagePort to deliveryDroneSystem.payloadPort {
            doc /* Package handover interface between the customer and the system. */
        }
        interface energySupplyInterface :> asis connect energySupply.energyPort to deliveryDroneSystem.energyPort {
            doc
            /* Electrical energy supply interface between the energy supply system and the delivery drone system. */
        }

    }
    #systemContext part def DeliveryDroneSystemContextImpl :> DeliveryDroneSystemContext {
        doc
        /* The white box brownfield context: adds the internal structure of the
         * existing delivery drone system. */
        #system part deliveryDroneSystemImpl : DeliveryDroneSystemImpl :>> deliveryDroneSystem {
            doc
            /* The existing delivery drone system as a white box. */
        }
    }
    part def DeliveryDroneSystem {
        doc
        /* Black box definition of the existing delivery drone system with its
         * external interfaces. */
        port operatorPort {
            doc
            /* Interface to the operator, who sends delivery orders to the system
             * and monitors its operation. */
            in item order : DeliveryDroneDomainLibrary::Items::DeliveryOrder;
        }
        port payloadPort {
            doc
            /* Package handover interface: the system receives the parcel from the
             * sender and hands it over to the customer at the destination. */
            in item pkgIn : DeliveryDroneDomainLibrary::Items::Parcel;
            out item pkgOut : DeliveryDroneDomainLibrary::Items::Parcel;
        }
        port landingZonePort {
            doc
            /* Physical interface to the landing zone where the drones take off,
             * land, and pick up or drop off packages. */
        }
        port environmentPort {
            doc
            /* Exposure to environmental conditions such as wind, rain, and
             * temperature that act on the system. */
        }
        port energyPort {
            doc
            /* Electrical energy supply of the system, e.g., for charging the
             * drone batteries at the drone docks. */
            in item energy : DeliveryDroneDomainLibrary::Items::Energy;
        }
    }
    part def DeliveryDroneSystemImpl :> DeliveryDroneSystem {
        doc
        /* White box definition of the existing delivery drone system: a fleet of
         * drones, a control station, and docks where the drones are charged. */
        part drones[1..*] : DeliveryDrone {
            doc
            /* The fleet of delivery drones. */
        }
        part controlStation {
            doc
            /* The ground station from which the operator supervises the fleet. */
        }
        part droneDocks[1..*] {
            doc
            /* Ground docks where drones park and recharge between flights. */
        }

        connect drones to droneDocks;
        connect drones to controlStation;
        connect droneDocks to controlStation;

        interface connect landingZonePort to drones.landingZonePort;
    }
    part def DeliveryDrone {
        doc
        /* An existing electric delivery drone of the current platform. */
        part engines[4..8] {
            doc
            /* Electric engines; the number depends on the drone variant. */
        }
        part battery {
            doc
            /* Rechargeable battery; today it is charged at the drone docks only. */
        }
        part body {
            doc
            /* Airframe carrying all other components. */
        }
        part payloadAttachment {
            doc
            /* Mount for the package to be delivered. */
        }
        part controlUnit {
            doc
            /* Onboard computer for navigation and communication. */
        }

        connect engines to body;
        connect engines to battery;
        connect battery to body;
        connect payloadAttachment to body;
        connect battery to controlUnit;
        connect controlUnit to body;

        port landingZonePort;
    }
}
