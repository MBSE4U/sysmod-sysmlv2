package SYSMOD4AI {
    doc
    /*
     * SYSMOD4AI: AI-assisted extension for SYSMOD v5
     *
     * Version v5.1.8
     *
     * Adds machine-readable AI instructions on top of the core SYSMOD library, so an AI assistant can
     * create, validate, and explain SYSMOD artifacts directly from this model — with no dependency on
     * any particular AI tool's skill, plugin, or extension mechanism. It is kept as a separate package
     * from SYSMOD so the core methodology library stays free of AI-specific concerns; import this
     * package in addition to SYSMOD only where AI assistance is wanted.
     *
     * Contents:
     * - metadata def AI: the attributes an AI assistant reads to work with one SYSMOD element —
     *   create_questions, create_prompt, and validation_prompt for the elicit/create/validate
     *   workflow (run together via perform_prompt), plus story_prompt and slide_prompt for explaining
     *   any selected element to non-technical stakeholders.
     * - AIProject: a template that attaches an AI metadata usage to each of Project's main artifacts,
     *   in SYSMOD order, forming a complete AI-assisted workflow across the whole project. AIProject
     *   is not meant to be specialized by real projects — a real project stays a plain #project
     *   occurrence def (or :> Project), independent of SYSMOD4AI. An AI assistant instead applies a
     *   given AI metadata usage's prompts to the identically-named/-roled feature on that real
     *   project (e.g. AIProject::problemStatementAI's prompts apply to any project's own
     *   problemStatement), matched by feature identity rather than by inheritance from AIProject.
     *
     * Licensed under the Apache License, Version 2.0 (the "License");
     * you may not use this file except in compliance with the License.
     * You may obtain a copy of the License at
     *
     * http://www.apache.org/licenses/LICENSE-2.0
     *
     * Unless required by applicable law or agreed to in writing, software
     * distributed under the License is distributed on an "AS IS" BASIS,
     * WITHOUT WARRANTIES OR CONDITIONS OF ANY KIND, either express or implied.
     * See the License for the specific language governing permissions and
     * limitations under the License.
     *
     * Copyright 2026, MBSE4U, Tim Weilkiens
     */

    private import SYSMOD::*;

    metadata def AI {
        doc
        /* Machine-readable AI instructions attached to SYSMOD artifacts. perform_prompt is the entry
         * point: an AI assistant executes it to run the fixed elicit/create/validate workflow over
         * this metadata's own create_questions, create_prompt, and validation_prompt for the single
         * SYSMOD element this metadata annotates. story_prompt and slide_prompt are separate, on-demand
         * entry points that retell any element the user selects for stakeholders who do not read SysML
         * notation: story_prompt as a plain-language narrative, slide_prompt as a single presentation
         * slide.
         * This metadata is self-contained and AI-tool-agnostic: any AI assistant that can read this
         * library follows these workflows directly from perform_prompt, story_prompt, and slide_prompt,
         * without needing a tool-specific skill, plugin, or extension file.
         * An AI metadata usage attached here under AIProject (e.g. problemStatementAI) is applied to the
         * identically-named feature on any real #project occurrence — matched by feature identity, not by that
         * project specializing AIProject.
         * Each AI metadata usage documents its own "When to use" / "When not to use" section in its own doc
         * comment, in the style of an AI-assistant skill's trigger/skip conditions, so these elements can be
         * turned into Claude Skills or equivalent skill definitions for other LLM platforms.
         */
        attribute name : ScalarValues::String {
            doc
            /* Unique identifier of the AI skill, for example, 'sysmod-problem-statement'. */
        }
        attribute create_prompt : ScalarValues::String {
            doc
            /* Step-by-step instructions for an AI assistant to create the annotated artifact. */
        }
        attribute create_questions : ScalarValues::String [*] {
            doc
            /* Questions the AI assistant can ask the user to elicit missing information. */
        }
        attribute validation_prompt : ScalarValues::String {
            doc
            /* Instructions for an AI assistant to verify and validate the annotated artifact against the SYSMOD rules. */
        }
        attribute perform_prompt : ScalarValues::String = "Perform the AI workflow for each single SYSMOD element, in this order:
            1. Elicit — ask the user only the entries of create_questions that are not already answered by the request or by the existing model.
            2. Create — execute create_prompt step by step to author or update the annotated element.
            3. Validate — run validation_prompt against the result and report findings grouped as errors, warnings, and suggestions before presenting the element as final; apply corrections and re-run validation_prompt if the user asks for it.
            Use only this metadata's own create_questions, create_prompt, and validation_prompt for this element." {
            doc
            /* Single, ready-to-run prompt that performs the elicit/create/validate workflow for the one SYSMOD
             * element this metadata annotates. An AI assistant can execute this attribute directly instead of
             * composing create_questions, create_prompt, and validation_prompt itself. Every AI metadata usage
             * inherits this default; override it only if a specific artifact needs a different orchestration.
             */
        }
        attribute story_prompt : ScalarValues::String = "Explain a SysML v2 element as a short natural-language story for a stakeholder who does not read modeling notation.
            1. Take the element the user has selected or named; if none is given, use the element this metadata annotates.
            2. Read the element's name, doc comments, and its immediate relationships in the model (e.g., what it frames, satisfies, subsets, is composed of, or is connected to).
            3. Retell it as a short narrative in the stakeholder's own language: who or what it represents, why it exists, and how it fits into the surrounding project story (e.g., 'This describes the problem the project owner asked us to solve, which is that...').
            4. Do not use SysML v2 keywords, notation, or diagrams, and avoid modeling jargon (e.g., 'part usage', 'subsets', 'occurrence') unless the user explicitly asks for the technical mapping alongside the story.
            5. Ground the story only in what is actually present in the element and its documented relationships — do not invent facts, causes, or consequences that are not in the model.
            6. Keep it concise: a few sentences to a short paragraph, unless the user asks for more detail.
            If the user selects a different element than the one this metadata annotates, and that element carries its own AI metadata, use that element's own story_prompt instead." {
            doc
            /* Prompt that lets an AI assistant explain any element the user selects — not only the one this
             * metadata annotates — as a plain-language story rather than SysML notation, for stakeholders who
             * find the formal model hard to read. Every AI metadata usage inherits this default; override it
             * only if a specific artifact needs a different narrative framing.
             */
        }
        attribute slide_prompt : ScalarValues::String = "Create a single presentation slide explaining a SysML v2 element for a stakeholder audience, in whatever slide or document format is available (e.g. PDF, PPTX, or an equivalent) so it can be dropped directly into a presentation.
            1. Take the element the user has selected or named; if none is given, use the element this metadata annotates.
            2. Read the element's name, doc comments, and its immediate relationships in the model (e.g., what it frames, satisfies, subsets, is composed of, or is connected to).
            3. Give the slide a short, descriptive title (not the raw SysML identifier) and a few plain-language bullet points covering what the element is, why it exists, and how it fits into the surrounding project — use the same plain-language framing as story_prompt, condensed to slide-appropriate bullets rather than a narrative.
            4. Do not use SysML v2 keywords, notation, or diagrams, and avoid modeling jargon (e.g., 'part usage', 'subsets', 'occurrence') unless the user explicitly asks for the technical mapping alongside the slide.
            5. Ground the slide only in what is actually present in the element and its documented relationships — do not invent facts, causes, or consequences that are not in the model.
            6. If the assistant is capable of generating or inserting images in the current environment, add at most one supporting image to the slide — an illustrative graphic of the element's real-world subject, not an invented SysML diagram or a fabricated technical drawing presented as fact; if image generation or insertion is not available, produce a text-only slide instead.
            7. Keep it to a single slide: one title, a handful of bullets, and at most one image — do not turn it into a multi-page or multi-slide document.
            8. If the user asks for a specific output format (e.g. PDF, PPTX, Keynote), produce that format; otherwise choose a format the current environment can actually generate and tell the user which one was used.
            If the user selects a different element than the one this metadata annotates, and that element carries its own AI metadata, use that element's own slide_prompt instead." {
            doc
            /* Prompt that lets an AI assistant turn any element the user selects — not only the one this
             * metadata annotates — into a single presentation-ready slide (PDF, PPTX, or another format the
             * environment supports) explaining it in plain language, for direct use in a stakeholder
             * presentation, adding a supporting image when the assistant is capable of it. Every AI metadata
             * usage inherits this default; override it only if a specific artifact needs different slide
             * content.
             */
        }
    }

    occurrence def AIProject :> Project {
        doc
        /* A template that enriches Project's main artifacts with AI metadata. AIProject is not meant to be
        * specialized by real projects — it exists only so every artifact's AI metadata is defined once, in one
        * coherent structure that mirrors SYSMOD order. Real projects stay plain #project occurrence defs (or
        * :> Project); an AI assistant applies a given artifact's AI metadata usage here (e.g. problemStatementAI)
        * to the correspondingly named feature on that real project, matched by feature identity, not inheritance.
        */
        metadata projectAI : AI {
            doc
            /* Scaffolds or validates the whole SYSMOD project: the root #project occurrence and,
             * optionally, chains through all of its main artifacts in SYSMOD order.
             *
             * When to use:
             * - Starting a brand-new SYSMOD project from scratch (kickoff), or the user asks to
             *   scaffold an entire project end to end in one go.
             * - Validating a whole project's structure and cross-artifact traceability chain,
             *   rather than just one artifact in isolation.
             *
             * When not to use:
             * - The user is working on a single artifact (e.g. only the problem statement, or
             *   only the stakeholders) — use that artifact's own AI metadata (e.g.
             *   problemStatementAI, projectStakeholdersAI) directly instead of going through the
             *   whole project.
             * - The project already exists and only the project owner needs to be identified or
             *   changed — use projectOwnerAI.
             */
            name = "sysmod-project";
            create_prompt =
                "1. Create the SysML v2 textual notation for the project definition using the SYSMOD-defined keyword: '#project occurrence def PROJECTNAME {}'
                2. Use the create_prompt of the AI metadata of the projectOwner to create the project owner of the project.
                3. If not given by the user, use the questions to get the name of the project and the location where the project should be added.
                4. Optionally continue with the other engineering artifacts in SYSMOD order (brownfieldContext, problemStatement, projectStakeholders, stakeholderNeeds, systemIdeaContext, systemObjectives, specificationContext, systemRequirementSpecification, the verification cases of the verificationContext, functionalContext, logicalContext, productContext, each with its Impl context, the verificationContext with its test systems, and subProjects) using the create_prompts of their AI metadata; use tradeStudiesAI for any architecture decision with alternatives.";
            create_questions = (
                "What is the name of the project?", 
                "Where should I add the project definition?",
                "Who is the project owner?"
            );
            validation_prompt =
                "Validate the project definition against the SYSMOD Project concept and report findings grouped as errors, warnings, and suggestions.
                Check:
                1. The project is defined as an occurrence definition annotated with the #project keyword or specializing Project.
                2. A projectOwner part usage is present and subsets projectStakeholders.
                3. A brownfieldContext part usage is present and typed by a SystemContext specialization; a brownfieldContextImpl part usage is present and specializes brownfieldContext.
                4. A problemStatement concern usage is present.
                5. A stakeholderNeeds concern usage is present and frames the problemStatement.
                6. A systemIdeaContext part usage is present and specializes brownfieldContext; a systemIdeaContextImpl part usage is present and specializes systemIdeaContext and brownfieldContextImpl.
                7. A specificationContext part usage is present and specializes systemIdeaContext; a specificationContextImpl part usage is present and specializes specificationContext and systemIdeaContextImpl.
                8. A systemRequirementSpecification requirement usage is present and frames stakeholderNeeds.
                9. A productContext part usage is present and specializes specificationContext; a productContextImpl part usage is present and specializes productContext and specificationContextImpl. A present functionalContextImpl part usage specializes functionalContext only; a present logicalContextImpl part usage specializes logicalContext and specificationContextImpl.
                10. The cross-artifact traceability chain is intact: problemStatement <- stakeholderNeeds <- systemRequirementSpecification, and satisfy relationships exist at the system idea and functional, logical, and product architecture levels.
                11. If both functionalContext and logicalContext are present, the functional2logical allocation is defined; if logicalContext is present, the logical2product allocation is defined. The same holds for the white box contexts and the functionalImpl2logicalImpl and logicalImpl2productImpl allocations.
                12. Verification cases are specified before the solution architecture: the verification case definitions of the specification have the black box specification system as subject; a present verificationContext is a system context whose system of interest is the system under verification, e.g., the product system, a prototype, or a simulation model, and its verification case usages subset verificationCases and are typed by the verification case definitions of the specification.
                13. If tradeStudies are present, each is typed by SYSMODTradeStudy and compares the variants of a project context that is a variation usage, and the variation is bound to the selected variant and carries Rationale metadata referring to the trade study.
                14. If subProjects are present, each develops a building block of the productContextImpl that is typed by the system of interest of a handover context, the project's requirementFlowDowns derive the handoverRequirements of each sub-project from the project's requirements, and after integration the productContextImpl binds each building block to the white box product system of its sub-project or documents that it stays a black box.
                Report each finding with the element name, the violated SYSMOD rule, and a concrete suggestion for correction.";
        }

        metadata defaultProcessAI : AI about defaultProcess {
            doc
            /* Guides the user step by step through the SYSMOD default process
             * (SYSMODProcesses::SYSMODDefaultProcess) and reports where a project stands in it:
             * setupProject, modelBrownfieldSystem, describeProblemStatement, identifyStakeholders,
             * identifyStakeholderNeeds, describeSystemIdea, defineSystemObjectives, specifySystem,
             * modelSolutionArchitecture (nested steps modelFunctionalArchitecture,
             * modelLogicalArchitecture, and modelProductArchitecture), modelSubProjects,
             * integrateSubProjects, specifyVerificationContext, and performVerification, plus
             * specifyTradeStudy, which has no fixed position. Verification is split in two:
             * specifySystem specifies the verification cases against the black box specification
             * system and returns the verification context with them, and specifyVerificationContext
             * adds the test systems and binds the verification cases to the system under verification.
             * performVerification executes them and documents the results in verification reports.
             *
             * When to use:
             * - The user asks what to do next in a SYSMOD project, how far the project has
             *   progressed, or wants to be walked through the SYSMOD steps in order.
             * - The user wants to run the whole SYSMOD process step by step, with a review
             *   point after each step, rather than scaffolding everything in one go.
             * - The user asks how the SYSMOD steps relate to the ISO/IEC/IEEE 15288 processes.
             *
             * When not to use:
             * - The user wants to scaffold or validate the project structure as a whole in one
             *   go — use projectAI.
             * - The user is working on a single artifact — use that artifact's own AI metadata
             *   (e.g. problemStatementAI, projectStakeholdersAI) directly.
             * - The user wants to define a project-specific process from scratch rather than
             *   follow or tailor the SYSMOD default process — this skill does not design new
             *   process models.
             */
            name = "sysmod-default-process";
            create_prompt =
                "1. Read the SYSMODDefaultProcess action definition in SYSMOD::SYSMODProcesses and its steps in succession order: setupProject, modelBrownfieldSystem, describeProblemStatement, identifyStakeholders, identifyStakeholderNeeds, describeSystemIdea, defineSystemObjectives, specifySystem, modelSolutionArchitecture (nested steps modelFunctionalArchitecture, modelLogicalArchitecture, modelProductArchitecture), modelSubProjects, integrateSubProjects, specifyVerificationContext, performVerification. The step specifyTradeStudy has no succession: offer it whenever a step faces an architecture decision with alternatives.
                2. Find the project. If no project exists, start with setupProject.
                3. Determine the current position in the process: for each step, check whether its outputs (the project features it flows into) already exist in the project and are valid. The first step whose outputs are missing or invalid is the next step.
                4. Execute the next step by delegating to the AI metadata of the project features it produces, using their create_questions, create_prompt, and validation_prompt:
                   - setupProject: projectAI and projectOwnerAI; set the project's purpose and the projectOwner's name from the process inputs projectPurpose and projectOwnerName.
                   - modelBrownfieldSystem: brownfieldContextAI, using the process input brownfieldArchitectureDescription (a description of the existing system).
                   - describeProblemStatement: problemStatementAI, using the process input problemStatementDescription and the projectOwner.
                   - identifyStakeholders: projectStakeholdersAI; optionally stakeholderPriorityMapAI.
                   - identifyStakeholderNeeds: stakeholderNeedsAI.
                   - describeSystemIdea: systemIdeaContextAI, using the process input systemIdeaArchitectureDescription.
                   - defineSystemObjectives: systemObjectivesAI (the system objectives with their measures of effectiveness and measures of performance).
                   - specifySystem: specificationContextAI (specification architecture and use cases), then systemRequirementSpecificationAI, then verificationCasesAI (nested step specifyVerificationCases: the verification case definitions with objective and verdict against the black box specification system, specified with the verification engineers before any solution architecture exists, and their usages in the project's verificationContext).
                   - modelSolutionArchitecture, with its nested steps in this order:
                     - modelFunctionalArchitecture (optional): functionalContextAI, using the process input functionalArchitectureDescription.
                     - modelLogicalArchitecture (optional): logicalContextAI, using the process input logicalArchitectureDescription.
                     - modelProductArchitecture: productContextAI, using the process input productArchitectureDescription.
                   - modelSubProjects (optional): subProjectsAI in the parent project, then handoverAI in each sub-project. Each sub-project then performs its own SYSMOD process.
                   - integrateSubProjects (optional): the integration part of subProjectsAI, once the product architectures of the sub-projects are available.
                   - specifyTradeStudy (optional, at any architecture decision with alternatives): tradeStudiesAI.
                   - specifyVerificationContext: verificationContextAI; type the project's verificationContext by a system context definition with the system under verification as system of interest (any system, e.g., the white box product system, a prototype, or a simulation model; the context may specialize an architecture context such as productContextImpl), add the test systems needed for the verification as actors (e.g., a test bench or a wind tunnel), and bind the subjects of the verification cases of the verificationContext to the system under verification. Do not create the verification cases anew; if a requirement has no verification case yet, go back to verificationCasesAI.
                   - performVerification: verificationContextAI; execute the verification cases of the verificationContext on the system under verification and add a verification report (item usage typed by VerificationReport, subsetting verificationReports of the verificationContext) per verification run with the verdict of each verification case, the verified requirements, and the evidence; its content is aligned with ISO/IEC/IEEE 15289. Do not change the verification cases; if one cannot be performed, report it and go back to specifyVerificationContext.
                5. Respect the inputs of each step as defined by the bindings and flows of SYSMODDefaultProcess and of the steps with nested steps: a step must only start when the project features it reads exist (e.g. identifyStakeholderNeeds needs the problemStatement and the projectStakeholders).
                6. Steps after setupProject are optional ([0..1] successions). Skip a step only when it does not apply (e.g. modelBrownfieldSystem for a pure greenfield project, the nested steps modelFunctionalArchitecture, modelLogicalArchitecture, and modelProductArchitecture of modelSolutionArchitecture, modelSubProjects and integrateSubProjects for a project without sub-projects, or specifyTradeStudy when a decision has no alternatives), and tell the user which step was skipped and why.
                7. After each step, show the user the result and the step's validation findings, and ask whether to continue with the next step, revise the current one, or stop.
                8. If the user asks how a step relates to ISO/IEC/IEEE 15288, answer from the #refinement dependencies in SYSMODProcesses (e.g. SpecifySystem refines ISO15288Processes::SystemRequirementsDefinition).
                9. Do not redefine the project's defaultProcess action usage unless the user explicitly asks to tailor the process; if so, redefine defaultProcess in the project with a specialization of SYSMODDefaultProcess and document every deviation in a doc comment.";
            create_questions = (
                "Which project should the process be applied to?",
                "Is it a greenfield project or does an existing (brownfield) system exist?",
                "Should I run all steps one after another, or only the next step?",
                "Which optional steps (brownfield system, functional architecture, logical architecture, product architecture) should be skipped?"
            );
            validation_prompt =
                "Validate the project's progress against the SYSMOD default process and report findings grouped as errors, warnings, and suggestions.
                Check:
                1. For each step of SYSMODDefaultProcess and each nested step with StepStatus (modelFunctionalArchitecture, modelLogicalArchitecture, modelProductArchitecture), report its status: done (outputs exist and pass the validation_prompt of the corresponding AI metadata), in progress (outputs exist but have validation errors), skipped, or open.
                2. No step is done while one of its inputs is missing or invalid (e.g. stakeholderNeeds without a problemStatement, systemRequirementSpecification without stakeholderNeeds, productContextImpl without a specificationContextImpl).
                3. setupProject: the project has a purpose and the projectOwner has a name.
                4. Only optional steps are skipped (modelBrownfieldSystem for greenfield projects, the nested steps modelFunctionalArchitecture, modelLogicalArchitecture, and modelProductArchitecture, modelSubProjects, integrateSubProjects, specifyTradeStudy); mandatory artifacts (problemStatement, projectStakeholders, stakeholderNeeds, systemIdeaContext, systemObjectives, specificationContext, systemRequirementSpecification) are not skipped.
                5. specifySystem: every requirement of the systemRequirementSpecification is verified by at least one verification case definition with the black box specification system as subject, and each of them has a verification case usage in the verificationContext subsetting verificationCases; specifyVerificationContext: the verificationContext has the system under verification as system of interest, contains the test systems, and the subjects of its verification cases are bound to the system under verification. Flag verification case definitions created in specifyVerificationContext that do not exist in the specification. performVerification: each verification report subsets verificationReports of the verificationContext and states the verdicts of the verification cases it covers.
                6. modelSubProjects and integrateSubProjects: every sub-project has a handover package and receives requirementFlowDowns from the project; specifyVerificationContext uses the integrated product system or documents which building blocks are still black boxes.
                7. specifyTradeStudy: every trade study passes the validation_prompt of tradeStudiesAI, and every architecture decision with documented alternatives has a trade study or a Rationale.
                8. If the project redefines defaultProcess, the redefinition is typed by a specialization of SYSMODDefaultProcess and documents its deviations from the default process.
                9. Name the next step to perform and the AI metadata to use for it.
                Report each finding with the step name, the affected element, the violated SYSMOD rule, and a concrete suggestion for correction.";
        }

        metadata projectOwnerAI : AI about projectOwner {
            doc
            /* Identifies or updates the single stakeholder who is in charge of the project (the
             * project owner) — a special ExtendedStakeholder with critical risk and low effort.
             *
             * When to use:
             * - The user names or asks about who owns, sponsors, or is accountable for the
             *   project.
             * - The project's problemStatement needs a stakeholder set and no projectOwner exists
             *   yet.
             *
             * When not to use:
             * - Identifying the broader stakeholder set beyond the owner — use
             *   projectStakeholdersAI.
             * - The user is describing what the owner (or anyone else) needs from the system —
             *   use stakeholderNeedsAI, not this skill.
             */
            name = "sysmod-project-owner";
            create_prompt =
                "1. If the user has provided a projectOwner, use it. If not, ask the user for the projectOwner using appropriate questions from the questions field.
                2. Create a concise projectOwner description.
                3. Create the SysML v2 textual notation for the projectOwner.
                4. If the user asks to insert the projectOwner into the SysML model, find the project and the projectOwner within the project. If no project exists, create one and insert the projectOwner into the project redefining the inherited projectOwner part usage. If the projectOwner already exists, update it.";
            create_questions = (
                "Who is the project owner?", 
                "Who is responsible for the project?"
            );
            validation_prompt =
                "Validate the projectOwner against the SYSMOD Project Owner concept and report findings grouped as errors, warnings, and suggestions.
                Check:
                1. Exactly one projectOwner part usage is present in the project, redefining the inherited projectOwner.
                2. The projectOwner subsets projectStakeholders and is typed by an ExtendedStakeholder specialization.
                3. The risk attribute is set to LevelKind::critical (the project owner always has critical risk).
                4. The effort attribute is set to LevelKind::low (the project owner is typically easy to reach).
                5. The categories attribute includes StakeholderCategoryKind::requirementOwner.
                6. The projectOwner is referenced as the stakeholder of the problemStatement.
                7. A meaningful name or doc comment identifies who the project owner is in the context of this project.
                Report each finding with the element name, the violated SYSMOD rule, and a concrete suggestion for correction.";
        }

        metadata brownfieldContextAI : AI about brownfieldContext {
            doc
            /* Documents the existing (as-is) system and its actors before the project starts —
             * the constraints and givens the project must work within.
             *
             * When to use:
             * - The user describes an existing system, legacy system, current state, or "as-is"
             *   situation that the project starts from.
             * - The project is brownfield (an existing system is being changed or replaced) and
             *   its current actors, subcomponents, or interfaces need to be captured before any
             *   solution is proposed.
             *
             * When not to use:
             * - The project is greenfield with no existing system to document — skip this skill
             *   and go straight to problemStatementAI / systemIdeaContextAI.
             * - The user is describing the new or changed system, its idea, or its architecture —
             *   that is systemIdeaContextAI (idea) or functionalContextAI / logicalContextAI /
             *   productContextAI (architecture), never this skill. Brownfield content must
             *   contain no solution elements.
             */
            name = "sysmod-brownfield-context";
            create_prompt =
                "1. Analyze the provided scenario and identify the brownfield system: the existing system, its relevant subcomponents, and all external actors (humans, external systems, environmental effects) that already interact with it before the project starts.
                2. Create a part definition for the brownfield context specializing SystemContext.
                3. Create a part definition for the brownfield system of interest.
                4. For each identified actor, create a part definition in a subpackage named 'Actors', if not already exists.
                5. For each identified actor, add a part usage defined by the corresponding part definition and subsetting the part usage 'actors' inherited from SystemContext.
                6. For the black box view, redefine the inherited soi part (within brownfieldContext) with an appropriately named and typed part definition. For the white box view, redefine the inherited soiImpl part (within brownfieldContextImpl, which specializes brownfieldContext) accordingly.
                7. Ensure the brownfield context reflects constraints and givens only — it must not include solution elements.
                8. Create the SysML v2 textual notation for the brownfieldContext and brownfieldContextImpl.
                9. If the user asks to insert the brownfieldContext into the SysML model, find the project and redefine the inherited brownfieldContext and brownfieldContextImpl part usages. If the project does not exist, create one first.";
            create_questions = (
                "What is the name of the existing system (system of interest)?",
                "Which external actors (users, operators, external systems, environments) interact with the existing system?",
                "Are there any known and preset subcomponents or subsystems of the existing system that are relevant?"
            );
            validation_prompt =
                "Validate the brownfieldContext and brownfieldContextImpl against the SYSMOD Brownfield Architecture concept and report findings grouped as errors, warnings, and suggestions.
                Check:
                1. The brownfieldContext part usage is present in the project and typed by a SystemContext specialization.
                2. At least one actor part usage subsetting actors is present, representing an external entity that interacts with the existing system.
                3. The soi part is redefined within brownfieldContext with a named part definition representing the existing system of interest (black box view).
                4. The brownfieldContextImpl part usage is present, specializes brownfieldContext, and redefines the soiImpl part representing the white box view of the existing system.
                5. Actor-system interfaces (actorSystemInterfaces) connect actor ports to system ports.
                6. The brownfield context contains only elements that exist before the project starts — no solution-specific parts, new system ideas, or future-state components.
                7. Each actor has a meaningful name and, ideally, a doc comment describing its role.
                Report each finding with the element name, the violated SYSMOD rule, and a concrete suggestion for correction.";
        }

        metadata problemStatementAI : AI about problemStatement {
            doc
            /* Frames the problem the project is meant to solve, as a concise elevator-pitch-style
             * statement based on the brownfield system's deficiencies — never a solution.
             *
             * When to use:
             * - The user wants to articulate, refine, or validate why the project exists — the
             *   problem, pain point, or opportunity being addressed.
             * - Starting a new project and no problem statement exists yet, or an existing one
             *   needs to be checked against the SYSMOD rules (e.g. no premature solution
             *   language).
             *
             * When not to use:
             * - The user is describing the solution, the new system's idea, or its architecture —
             *   use systemIdeaContextAI (or the architecture skills) instead; problemStatementAI
             *   never describes "how", only "why".
             * - The user wants individual stakeholder needs rather than the single overarching
             *   problem — use stakeholderNeedsAI.
             */
            name = "sysmod-problem-statement";
            create_prompt =
                "1. Follow the structure between engineering artifacts given by the SYSMOD library.
                2. Analyze the provided scenario. If it is forward engineering, identify the problem statement from the given scenario. If it is reverse engineering, identify the problem statement by identifying the problem that is solved by the given system.
                3. Create a concise elevator-pitch-style problem statement text (typically 150-250 words).
                4. Follow this format: 'How can we...'
                5. Ensure the problem statement text is based on the brownfieldContext. If the brownfieldContext is not available, create one that is implied by the problem statement text using the AI metadata about the brownfieldContext, except the user explicitly said that it is a greenfield project which has no brownfield.
                6. Ensure that the problem statement does not jump to the solution and describe it in advance.
                7. Ensure that the stakeholder projectOwner is set by subsetting the corresponding part usage in the project, if given. If it is not available, use the create_prompt of the AI metadata about the projectOwner to create one.
                8. If it is reverse engineering, create a satisfy relationship between the given system and the problem statement.
                9. Create the SysML v2 textual notation for the problemStatement.
                10. If the user asks to insert the problemStatement into the SysML model, find the project and the problemStatement within the project. If no project exists, create one and insert the problemStatement into the project redefining the inherited problemStatement concern usage. If the problemStatement already exists, update it.";
            create_questions = (
                "What is the core problem the system should solve?",
                "What are the main deficiencies or pain points of the existing (brownfield) system?"
            );
            validation_prompt =
                "Validate the problemStatement against the SYSMOD Problem Statement concept and report findings grouped as errors, warnings, and suggestions.
                Check:
                1. The problemStatement concern usage is present in the project, redefining the inherited problemStatement.
                2. The subject references the brownfieldContextImpl soiImpl (the existing system is the subject of the problem).
                3. The projectOwner is set as the stakeholder of the problemStatement.
                4. The priority attribute is set to LevelKind::critical.
                5. A doc comment is present containing the problem statement text.
                6. The problem statement text starts with 'How can we...' or an equivalent problem-framing phrase.
                7. The problem statement text describes the problem, not a solution — check for premature solution language (e.g., 'we will build', 'the new system shall', named technologies or architectures).
                8. The problem statement text references the brownfield system and its deficiencies.
                9. The problem statement text is concise (typically 150-250 words).
                10. If it is reverse engineering, a satisfy relationship exists between the existing system and the problemStatement.
                Report each finding with the element name, the violated SYSMOD rule, and a concrete suggestion for correction.";
        }

        metadata projectStakeholdersAI : AI about projectStakeholders {
            doc
            /* Identifies the individuals and organizations with an interest in the system
             * (beyond the project owner) and assesses each one's risk, effort, and category.
             *
             * When to use:
             * - The user asks who the users, customers, regulators, or other interested parties
             *   are, or wants to identify or prioritize/assess stakeholders.
             * - The brownfieldContext's actors need to be reflected as stakeholders, or a
             *   stakeholder list needs validating for completeness.
             *
             * When not to use:
             * - Identifying or updating specifically the project owner — use projectOwnerAI.
             * - Capturing what a stakeholder needs from the system — use stakeholderNeedsAI, not
             *   this skill.
             * - Visualizing already-identified stakeholders on a risk/effort map — use
             *   stakeholderPriorityMapAI once risk and effort are assessed here.
             */
            name = "sysmod-stakeholders";
            create_prompt =
                "1. Analyze the brownfieldContext and the problemStatement and identify all relevant stakeholders (individuals or organizations with an interest in the system).
                2. For each stakeholder, create a part definition specializing ExtendedStakeholder.
                3. Assess and set the risk (what is the risk of failure if this stakeholder is ignored?), effort (how much effort is needed to identify their concerns?), and one or more stakeholder categories (user, requirementOwner, expert, other) for each stakeholder.
                4. Add each stakeholder as a named part usage subsetting projectStakeholders inside the project, typed by the corresponding stakeholder definition.
                5. Create the SysML v2 textual notation for all stakeholder definitions and their usages within the project.
                6. If the user asks to insert the stakeholders into the SysML model, find the project and add or update the stakeholder part usages.";
            create_questions = (
                "Who are the primary users of the system?",
                "Which organizations or roles own or define the requirements?",
                "Are there regulatory bodies, standards authorities, or other external parties with an interest in the system?"
            );
            validation_prompt =
                "Validate the projectStakeholders against the SYSMOD Stakeholders concept and report findings grouped as errors, warnings, and suggestions.
                Check:
                1. At least one stakeholder part usage (beyond the projectOwner) subsets projectStakeholders.
                2. Each stakeholder part usage is typed by a part definition specializing ExtendedStakeholder.
                3. Each stakeholder definition has the risk attribute set to a non-default LevelKind value (i.e., not LevelKind::none).
                4. Each stakeholder definition has the effort attribute set to a non-default LevelKind value (i.e., not LevelKind::none).
                5. Each stakeholder definition has at least one category assigned from StakeholderCategoryKind.
                6. The set of stakeholders covers all actors present in the brownfieldContext — every actor should map to at least one stakeholder.
                7. At least one stakeholder with category requirementOwner is present (beyond the projectOwner).
                8. Each stakeholder has a doc comment or name that clearly identifies its role.
                9. No two stakeholders have identical risk, effort, and category values without a distinguishing doc comment explaining the distinction.
                Report each finding with the element name, the violated SYSMOD rule, and a concrete suggestion for correction.";
        }

        metadata stakeholderPriorityMapAI : AI about projectStakeholders {
            doc
            /* Renders the project's already-identified stakeholders as a derived risk/effort
             * priority map — an analysis view, not a persisted model element.
             *
             * When to use:
             * - The user asks to visualize, prioritize, or compare stakeholders by risk and
             *   effort, or wants a stakeholder map or matrix.
             * - Stakeholders already exist in projectStakeholders with risk and effort assigned
             *   (or the user is willing to supply missing values on request).
             *
             * When not to use:
             * - No stakeholders have been identified yet — use projectStakeholdersAI first.
             * - The user wants to add, remove, or change stakeholders, or change their
             *   risk/effort values — this skill must not introduce or alter stakeholder data,
             *   only visualize it.
             * - The user wants a persisted SysML model element — the map is a diagram/analysis
             *   artifact only.
             */
            name = "sysmod-stakeholder-priority-map";
            create_prompt =
                "1. Use the risk and effort attribute values of each stakeholder in projectStakeholders (typed by ExtendedStakeholder) to position it on a two-dimensional map: risk on the y axis (low to critical, bottom to top), effort on the x axis (low to high, left to right).
                2. Depict each stakeholder as a stakeholder symbol labeled with its name, placed in the map cell that matches its risk/effort combination.
                3. If two or more stakeholders share the same risk/effort combination, group their symbols within the same cell without overlapping.
                4. The stakeholder priority map is a derived view, not a new model element — it must not introduce new stakeholders or change existing risk/effort values. If a stakeholder has no risk or effort value assigned, ask the user for it or use the create_prompt of projectStakeholdersAI first to assess it.
                5. Render the map as a diagram (e.g., SVG or a described grid), not as SysML v2 textual notation, since it is an analysis artifact rather than a persisted model element.";
            create_questions = (
                "Which stakeholders (from projectStakeholders) should be included in the map?",
                "Do all included stakeholders already have risk and effort values assigned? If not, what are they?"
            );
            validation_prompt =
                "Validate the stakeholder priority map against the SYSMOD Stakeholder Priority Map concept and report findings grouped as errors, warnings, and suggestions.
                Check:
                1. Every stakeholder shown in the map corresponds to an actual part usage subsetting projectStakeholders in the project — no invented stakeholders.
                2. Every stakeholder in projectStakeholders with both risk and effort assigned is represented exactly once in the map — none silently omitted.
                3. Each stakeholder's position matches its risk (y axis) and effort (x axis) attribute values exactly.
                4. Stakeholders sharing the same risk/effort cell are all visible and distinguishable, not overlapping or hidden.
                5. The map does not introduce or imply risk/effort values that are not set on the underlying stakeholder definitions.
                Report each finding with the element name, the violated SYSMOD rule, and a concrete suggestion for correction.";
        }

        metadata stakeholderNeedsAI : AI about stakeholderNeeds {
            doc
            /* Derives each stakeholder's high-level needs from the problem statement and
             * stakeholder list — what they need the system to do or be, expressed at the intent
             * level, not as requirements.
             *
             * When to use:
             * - The user describes what stakeholders want, expect, or need from the system, in
             *   their own words.
             * - Stakeholders and the problem statement already exist and their needs must be
             *   captured or validated before deriving formal requirements.
             *
             * When not to use:
             * - The user is stating a verifiable, solution-neutral requirement rather than an
             *   intent-level need — use systemRequirementSpecificationAI.
             * - No stakeholders or problem statement exist yet — use projectStakeholdersAI /
             *   problemStatementAI first, since needs must trace back to both.
             */
            name = "sysmod-stakeholder-needs";
            create_prompt =
                "1. Analyze the projectStakeholders and the problemStatement and derive the high-level needs of each stakeholder.
                2. For each stakeholder need, create a concern definition with the brownfield system as its first parameter (subject) and a typed stakeholder parameter for each stakeholder the need comes from. Create a concern usage redefining stakeholderNeeds that binds the subject to brownfieldContextImpl.soiImpl and binds each stakeholder parameter to the corresponding part usage in projectStakeholders.
                3. Ensure each need is expressed from the stakeholder's perspective and describes what they need the system to do or be, not how.
                4. Do not express needs as solution-specific requirements; keep them at the stakeholder intent level.
                5. Create the SysML v2 textual notation for the stakeholderNeeds.
                6. If the user asks to insert the stakeholderNeeds into the SysML model, find the project and redefine the inherited stakeholderNeeds concern usage. If the project does not exist, create one first.";
            create_questions = (
                "What does each stakeholder group need the system to do or be?",
                "Are there any known constraints or non-functional needs (safety, cost, compliance) expressed by stakeholders?"
            );
            validation_prompt =
                "Validate the stakeholderNeeds against the SYSMOD Stakeholder Needs concept and report findings grouped as errors, warnings, and suggestions.
                Check:
                1. The stakeholderNeeds concern usage is present in the project, redefining the inherited stakeholderNeeds.
                2. The stakeholderNeeds frames the problemStatement.
                3. The subject of stakeholderNeeds references the brownfieldContextImpl soiImpl.
                4. At least one stakeholder need is defined as a concern usage nested inside stakeholderNeeds. Each stakeholder need definition declares a subject typed by the brownfield system as its first feature, and each nested concern usage redefines that subject and binds it to the brownfieldContextImpl soiImpl, before any stakeholder declaration.
                5. Each stakeholder need declares at least one stakeholder parameter, and each such parameter in the need usage is bound to a part usage subsetting projectStakeholders.
                6. Each need is expressed at the stakeholder intent level — check for premature solution or design language (e.g., specific technologies, implementation details, design choices).
                7. The set of stakeholder needs covers all projectStakeholders — no stakeholder group should be left without at least one associated need.
                8. Each need has a doc comment or name that is understandable without reading the full model.
                Report each finding with the element name, the violated SYSMOD rule, and a concrete suggestion for correction.";
        }

        metadata systemIdeaContextAI : AI about systemIdeaContext {
            doc
            /* Develops the high-level system idea — an elevator-pitch-style outline of the new or
             * changed system that answers the problem statement, at a conceptual level with no
             * architecture yet.
             *
             * When to use:
             * - The user proposes, sketches, or asks for a high-level concept, approach, or "big
             *   idea" for solving the problem.
             * - A problem statement exists and the project is ready to move from "why" to a
             *   first-cut "what".
             *
             * When not to use:
             * - The user wants detailed architecture, components, or technology choices — use
             *   functionalContextAI, logicalContextAI, or productContextAI instead; the system
             *   idea stays conceptual.
             * - The user is describing the existing/as-is system — use brownfieldContextAI, not
             *   this skill.
             * - No problemStatement exists yet — create one first with problemStatementAI.
             */
            name = "sysmod-system-idea";
            create_prompt =
                "1. Based on the problemStatement, develop a high-level system idea: an elevator-pitch-style outline of the new or changed system that solves the stated problem.
                2. Specialize brownfieldContext by redefining the soi part (black box view) with a named system idea definition, within systemIdeaContext. Specialize systemIdeaContext and brownfieldContextImpl by redefining the soiImpl part (white box view) with the matching system idea implementation, within systemIdeaContextImpl. The systemIdeaSystemImpl must include a satisfy relationship to the problemStatement.
                3. Add any additional actors that are introduced by the system idea and are not already present in the brownfieldContext.
                4. Keep the system idea at a conceptual level — no detailed architecture or design decisions.
                5. Create the SysML v2 textual notation for the systemIdeaContext and systemIdeaContextImpl.
                6. If the user asks to insert the systemIdeaContext into the SysML model, find the project and redefine the inherited systemIdeaContext and systemIdeaContextImpl part usages. If the project does not exist, create one first.";
            create_questions = (
                "What is the high-level concept or approach for the new or changed system?",
                "Are there any new actors introduced by the system idea that do not exist in the brownfield?"
            );
            validation_prompt =
                "Validate the systemIdeaContext and systemIdeaContextImpl against the SYSMOD System Idea concept and report findings grouped as errors, warnings, and suggestions.
                Check:
                1. The systemIdeaContext part usage is present in the project and specializes brownfieldContext.
                2. The soi part is redefined within systemIdeaContext with a named system idea definition that specializes the brownfield soi.
                3. The systemIdeaContextImpl part usage is present, specializes systemIdeaContext and brownfieldContextImpl, and redefines the soiImpl part, specializing the system idea soi.
                4. All actors from the brownfieldContext are inherited or explicitly redefined — no brownfield actor should silently disappear.
                5. Any new actors introduced by the system idea are added as additional actor part usages.
                6. The system idea stays at a conceptual level — check for premature architecture or design detail (e.g., specific components, protocols, or technologies named in the soiImpl structure).
                7. A doc comment on the soiImpl describes the system idea in elevator-pitch style.
                Report each finding with the element name, the violated SYSMOD rule, and a concrete suggestion for correction.";
        }

        metadata specificationContextAI : AI about specificationContext {
            doc
            /* Refines the system idea into a specification-level system with use cases
             * describing how actors interact with it, still as a black box/white box context (no
             * requirements yet).
             *
             * When to use:
             * - The user wants to define or validate use cases, actor interactions, or the
             *   specification-level system definition.
             * - A system idea exists and is mature enough to describe concrete interactions with
             *   actors.
             *
             * When not to use:
             * - The user wants the initial high-level concept — use systemIdeaContextAI first.
             * - The user is stating formal, verifiable requirements — use
             *   systemRequirementSpecificationAI; this skill defines use cases and actors, not
             *   requirement text.
             * - The user is describing internal architecture or design — that comes later, in
             *   functionalContextAI / logicalContextAI / productContextAI.
             */
            name = "sysmod-specification-context";
            create_prompt =
                "1. Specialize systemIdeaContext by redefining the soi part (black box view) with a specification-level system definition, within specificationContext. Specialize specificationContext and systemIdeaContextImpl by redefining the soiImpl part (white box view) with the matching specification implementation, within specificationContextImpl.
                2. Identify and add any actors and interfaces at the system boundary that become visible during requirements analysis to the specificationContext (black box). Add subparts or attributes of the system that use cases and requirements refer to, e.g., the drones of a drone delivery system, to the soiImpl within specificationContextImpl (white box), not to the black box soi.
                3. Add system use cases to the specificationContext that describe how actors interact with the system of interest at the specification level.
                4. Each use case definition declares the specification system as its first parameter (subject) and a typed actor parameter for each participating actor. Each use case usage in the specificationContext subsets its subject from the context's soi and binds each actor parameter to the context's actor part usage.
                5. Create the SysML v2 textual notation for the specificationContext and specificationContextImpl, including actor parts and use case usages.
                6. If the user asks to insert the specificationContext into the SysML model, find the project and redefine the inherited specificationContext and specificationContextImpl part usages.";
            create_questions = (
                "Which use cases describe how actors interact with the system?",
                "Are there additional actors that become visible at the specification level, or subparts and attributes of the system that the use cases and requirements refer to?"
            );
            validation_prompt =
                "Validate the specificationContext and specificationContextImpl against the SYSMOD Specification Context concept and report findings grouped as errors, warnings, and suggestions.
                Check:
                1. The specificationContext part usage is present in the project and specializes systemIdeaContext.
                2. The soi part is redefined within specificationContext with a named specification system definition that specializes the system idea soi.
                3. The specificationContextImpl part usage is present, specializes specificationContext and systemIdeaContextImpl, and redefines the soiImpl part, specializing the specification soi.
                4. At least one use case usage is present in the specificationContext, referencing the specificationSystem as its subject.
                5. Each use case has at least one actor parameter, and in the specificationContext every actor parameter is bound to an actor part usage subsetting actors.
                6. Each use case has a meaningful name and doc comment describing the interaction goal.
                7. All actors from the systemIdeaContext are inherited or redefined — no actor should silently disappear.
                8. The specificationContext does not contain solution elements or subparts of the system — it should remain a black box view of the system; subparts and attributes used by use cases and requirements are defined in the specificationContextImpl.
                Report each finding with the element name, the violated SYSMOD rule, and a concrete suggestion for correction.";
        }

        metadata systemObjectivesAI : AI about systemObjectives {
            doc
            /* Defines the system objectives — the measurable goals of the system idea that
             * frame the stakeholder needs and are the basis for the system requirements and
             * for validation.
             *
             * When to use:
             * - The user states what the new or changed system must achieve and how success is
             *   measured (e.g. "deliver in half the time", "cut the cost per delivery by 30 %").
             * - A system idea and the stakeholder needs exist and the project must agree on
             *   measurable goals before the system requirements are elaborated.
             *
             * When not to use:
             * - The user describes the concept of the solution itself — use systemIdeaContextAI.
             * - The user states a verifiable requirement on the specification system — use
             *   systemRequirementSpecificationAI.
             */
            name = "sysmod-system-objectives";
            create_prompt =
                "1. Based on the systemIdeaContext, the problemStatement, and the stakeholderNeeds, derive the measurable goals of the system idea.
                2. For each objective, create a concern definition specializing SystemObjective with the system idea as its first parameter (subject). Specify its measures of effectiveness (MOE, how well the system achieves the objective from the stakeholders' perspective) as attributes subsetting measuresOfEffectiveness, and, if known, its measures of performance (MOP, system performances that contribute to an MOE) as attributes subsetting measuresOfPerformance. State the target values as attributes and as required constraints on the measures. Create a concern usage redefining systemObjectives that binds the subject to the systemIdeaContext soi, binds the projectOwner, and nests one concern usage per objective.
                3. The systemObjectives frame the stakeholderNeeds; each objective addresses at least one stakeholder need. The objectives direct the development: the system requirements reflect them, but no requirement frames them and no system satisfies them directly.
                4. Keep the objectives solution-neutral below the level of the system idea — no architecture or design decisions.
                5. Create the SysML v2 textual notation for the systemObjectives.
                6. If the user asks to insert the systemObjectives into the SysML model, find the project and redefine the inherited systemObjectives concern usage.";
            create_questions = (
                "What must the new or changed system achieve compared to today?",
                "How is success measured, and what are the target values?"
            );
            validation_prompt =
                "Validate the systemObjectives against the SYSMOD System Objectives concept and report findings grouped as errors, warnings, and suggestions.
                Check:
                1. The systemObjectives concern usage is present in the project, redefining the inherited systemObjectives.
                2. The systemObjectives frame the stakeholderNeeds.
                3. The subject references the systemIdeaContext soi, and the stakeholder is the projectOwner.
                4. At least one objective is defined as a concern usage nested inside systemObjectives.
                5. Each objective is measurable — it is typed by SystemObjective, has at least one measure of effectiveness (subsetting measuresOfEffectiveness) with a target value; flag vague goals without a threshold (e.g., 'faster', 'cheaper'). Measures of performance subset measuresOfPerformance.
                6. Each objective is traceable to at least one stakeholder need.
                7. Each objective is solution-neutral — no architecture or design decisions.
                Report each finding with the element name, the violated SYSMOD rule, and a concrete suggestion for correction.";
        }

        metadata systemRequirementSpecificationAI : AI about systemRequirementSpecification {
            doc
            /* Derives verifiable, solution-neutral system requirements from the stakeholder needs
             * and specification-level use cases, each with obligation, stability, and motivation.
             *
             * When to use:
             * - The user wants to state, refine, or validate formal system requirements.
             * - Stakeholder needs and/or use cases already exist and need to be turned into
             *   verifiable requirement statements traceable back to them.
             *
             * When not to use:
             * - The user is expressing an intent-level want in their own words, not yet a
             *   verifiable requirement — use stakeholderNeedsAI instead.
             * - The user is proposing a design or technology choice — requirements must stay
             *   solution-neutral; route architecture decisions to functionalContextAI /
             *   logicalContextAI / productContextAI.
             */
            name = "sysmod-system-requirements";
            create_prompt =
                "1. Derive system requirements from the stakeholderNeeds and the systemObjectives, framed by the stakeholderNeeds and referencing the white box specification system (specificationSystemImpl, the soiImpl of specificationContextImpl) as subject. Each measurable system objective is reflected in at least one requirement with the target value.
                2. For each requirement, create a requirement usage or definition specializing ExtendedRequirement. Set obligation (mandatory/optional), stability (stable/unstable), and a brief motivation. Declare the specification system as the first parameter (subject) and a typed stakeholder parameter for the stakeholders of the framed need. In the root requirement, bind each nested requirement usage's subject to the root subject or, for a requirement on a subpart of the system, to that subpart of the root subject (e.g., 'requirement maxPayloadMass : MaxPayloadMass { subject :>> deliveryDrone :> deliveryDroneSystem.drones; }').
                3. Ensure each requirement is verifiable, unambiguous, and solution-neutral where possible.
                4. Group requirements logically (e.g., functional, performance, safety, interface) using nested requirement usages if appropriate.
                5. Create the SysML v2 textual notation for the systemRequirementSpecification.
                6. If the user asks to insert the systemRequirementSpecification into the SysML model, find the project and redefine the inherited systemRequirementSpecification requirement usage.";
            create_questions = (
                "What are the key functional requirements of the system?",
                "Are there non-functional requirements (performance, safety, reliability, compliance)?",
                "Which requirements are mandatory and which are optional?"
            );
            validation_prompt =
                "Validate the systemRequirementSpecification against the SYSMOD System Requirements concept and report findings grouped as errors, warnings, and suggestions.
                Check:
                1. The systemRequirementSpecification requirement usage is present in the project, framing the stakeholderNeeds.
                2. The subject references the specificationContextImpl soiImpl (the white box specification system is the subject of the requirements), and the subject of each nested requirement is bound to the root subject or one of its subparts.
                3. At least one system requirement is defined as a nested requirement usage or definition.
                4. Each requirement specializes ExtendedRequirement and has the obligation attribute set (not ObligationKind::none).
                5. Each requirement has the stability attribute set (not StabilityKind::none).
                6. Each requirement has a non-empty motivation attribute explaining why the requirement exists.
                7. Each requirement is traceable to at least one stakeholder need (via frame or derive relationships, or doc comment reference).
                8. Each requirement text is verifiable — check for vague qualifiers without measurable criteria (e.g., 'fast', 'easy', 'reliable' without a threshold).
                9. Each requirement is solution-neutral — check for implementation-specific language (named technologies, specific designs) that constrain the solution unnecessarily.
                10. The set of requirements covers all defined use cases — every use case should be reflected in at least one functional requirement.
                Report each finding with the element name, the violated SYSMOD rule, and a concrete suggestion for correction.";
        }

        metadata verificationCasesAI : AI about verificationContext::verificationCases {
            doc
            /* Specifies the verification cases of the system requirements against the black box
             * specification system while the system is specified — before any solution
             * architecture exists — so that verification engineers and systems engineers
             * discuss the verification in SysML rather than in a separate test language
             * (nested step specifyVerificationCases of specifySystem). The verification case
             * usages are owned by the verification context of the project.
             *
             * When to use:
             * - System requirements exist, and the user wants to state how they will be
             *   verified: the objective, the verdict, and the test procedure at the system
             *   boundary.
             * - A verification engineer joins the project early and wants to review the
             *   requirements for verifiability or to agree on acceptance criteria.
             *
             * When not to use:
             * - The user wants to add test systems (test benches, wind tunnels) or to bind a
             *   verification case to the product architecture — use verificationContextAI.
             * - The requirement itself is not yet verifiable — fix it with
             *   systemRequirementSpecificationAI first.
             */
            name = "sysmod-verification-cases";
            create_prompt =
                "1. For each requirement of the systemRequirementSpecification, create at least one verification case definition (verification def) in the specification package of the system, e.g., in a nested package Verification next to the requirements.
                2. Declare the subject of each verification case definition typed by the black box specification system definition (the type of specificationContext.soi), not by a definition of the functional, logical, or product architecture.
                3. Declare the verified requirements as requirement usages typed by the requirement definitions, and state the objective with 'objective { verify <requirement>; }'. Leave the subjects of the verified requirements unbound when they refer to internal elements of the system that the black box does not contain; the verification context binds them.
                4. Return the verdict, e.g., 'return verdict = VerificationCases::PassIf(<requirement>.result);', and outline the test procedure as actions at the system boundary where helpful.
                5. In the project's verificationContext, create one verification case usage per verification case definition, typed by it and subsetting verificationCases. Redefine the verificationContext in the project if it is not yet present; the test systems and the binding to the system under verification follow in specifyVerificationContext (verificationContextAI).
                6. Name the VerificationEngineer (ISO15288Processes::Stakeholders) as stakeholder who specifies the verification cases together with the RequirementsEngineer (concern VerificationCoverage); add a project stakeholder playing this role if the user names one.
                7. Create the SysML v2 textual notation for the verification case definitions and usages.";
            create_questions = (
                "Which requirements should be verified first, and by which method (test, analysis, inspection, demonstration)?",
                "What is the pass criterion of each verification case?",
                "Who are the verification engineers who specify the verification cases with the systems engineers?"
            );
            validation_prompt =
                "Validate the verification cases of the verificationContext against the SYSMOD verification concept and report findings grouped as errors, warnings, and suggestions.
                Check:
                1. Each verification case usage of the verificationContext subsets verificationCases and is typed by a verification case definition.
                2. The subject of each verification case definition is typed by the black box specification system definition.
                3. Each verification case definition has an objective that verifies at least one requirement of the systemRequirementSpecification, and a verdict.
                4. Every requirement of the systemRequirementSpecification is verified by at least one verification case (VerificationCoverage).
                5. No verification case definition depends on elements of the functional, logical, or product architecture.
                Report each finding with the element name, the violated SYSMOD rule, and a concrete suggestion for correction.";
        }

        metadata functionalContextAI : AI about functionalContext {
            doc
            /* Defines the optional functional architecture — technology-independent
             * functions/actions derived from the specification's black box view, without
             * depending on physical structure.
             *
             * When to use:
             * - The user wants to decompose the system into functions or behaviors (e.g. using
             *   the FAS method), independent of implementation technology.
             * - System requirements exist and the project has decided a functional architecture
             *   is needed (it is optional in SYSMOD).
             *
             * When not to use:
             * - The project doesn't need a functional decomposition — this artifact is optional;
             *   skip it and go straight to logicalContextAI / productContextAI if so.
             * - The user is naming concrete technologies, components, or physical structure —
             *   that belongs in logicalContextAI (technology-independent building blocks) or
             *   productContextAI (concrete parts), not here.
             */
            name = "sysmod-functional-architecture";
            create_prompt =
                "1. If a functional architecture is required, specialize specificationContext (black box view) within functionalContext. Neither functionalContext nor functionalContextImpl specializes specificationContextImpl — the functional architecture must not depend on the physical internal structure of the system.
                2. Redefine the inherited functionalSystem part (which redefines the black box specification soi) as the root of the functional architecture (e.g., developed with the FAS method). It inherits the system ports, so functions can be related to the system's external interfaces. Define the top-level functions of the system as action usages within the functionalSystem.
                3. Specialize functionalContext within functionalContextImpl (white box view) by redefining the inherited functionalSystemImpl part. Define the functional blocks as part usages within the functionalSystemImpl that perform the functions.
                4. If allocations to the logical architecture are known, note them; the nested step modelLogicalArchitecture of modelSolutionArchitecture creates the functional2logical allocation (black box contexts) and the functionalImpl2logicalImpl allocation (white box contexts) in the project.
                5. Create the SysML v2 textual notation for the functionalContext and the functionalContextImpl.
                6. If the user asks to insert them into the SysML model, find the project and redefine the inherited functionalContext and functionalContextImpl part usages (note: multiplicity is [0..1]).";
            create_questions = (
                "Is a functional architecture required for this project?",
                "What are the top-level functions the system must perform?",
                "Should the functional architecture follow the FAS method or another approach?"
            );
            validation_prompt =
                "Validate the functionalContext against the SYSMOD Functional Architecture concept and report findings grouped as errors, warnings, and suggestions.
                Check:
                1. If present, the functionalContext part usage specializes specificationContext, and the functionalContextImpl part usage specializes functionalContext but not specificationContextImpl.
                2. A functionalSystem part is present as the root of the functional architecture, redefining the black box specification soi; a functionalSystemImpl part redefines the functionalSystem.
                3. At least one top-level function is defined as an action usage within the functionalSystem, and the functional blocks are part usages within the functionalSystemImpl.
                4. Each top-level function is traceable to at least one system requirement (via satisfy, refine, or doc comment reference).
                5. Functions are technology-independent — check for implementation-specific naming or structure that belongs in the logical or product architecture.
                6. If a logicalContext is present in the project, a functional2logical allocation is defined connecting the functionalContext to the logicalContext; if a logicalContextImpl is present, a functionalImpl2logicalImpl allocation connects the functionalContextImpl to the logicalContextImpl.
                7. The functionalSystemImpl contains only functional blocks — no physical structure of the system, which belongs in the logical or product contexts.
                Report each finding with the element name, the violated SYSMOD rule, and a concrete suggestion for correction.";
        }

        metadata logicalContextAI : AI about logicalContext {
            doc
            /* Defines the optional logical architecture — technology-independent building blocks
             * that realize the functional architecture (or the requirements directly), without
             * naming concrete technologies.
             *
             * When to use:
             * - The user wants to define logical components, subsystems, or a technology-
             *   independent partitioning of the solution.
             * - A functional architecture (or the requirements) exists and the project has
             *   decided a logical architecture is needed (it is optional in SYSMOD).
             *
             * When not to use:
             * - The project doesn't need a logical layer — this artifact is optional; go straight
             *   to productContextAI if so.
             * - The user names concrete/physical components, vendors, or deployment details —
             *   that belongs in productContextAI, not here.
             * - The user wants functions or behaviors rather than structural building blocks —
             *   use functionalContextAI.
             */
            name = "sysmod-logical-architecture";
            create_prompt =
                "1. If a logical architecture is required, specialize specificationContext (black box view) within logicalContext by redefining the inherited logicalSystem part (the redefined black box soi).
                2. Specialize logicalContext and specificationContextImpl within logicalContextImpl (white box view) by redefining the inherited logicalSystemImpl part. Define logical components as part usages within logicalSystemImpl, representing technology-independent building blocks that realize the functional architecture.
                3. If a functional architecture is present, create the functional2logical allocation (black box contexts) and the functionalImpl2logicalImpl allocation (white box contexts) by redefining the inherited allocation usages in the project, and allocate the functional blocks to the logical components within functionalImpl2logicalImpl.
                4. If allocations to the product architecture are known, note them; the nested step modelProductArchitecture of modelSolutionArchitecture creates the logical2product and logicalImpl2productImpl allocations in the project.
                5. Create the SysML v2 textual notation for the logicalContext and the logicalContextImpl.
                6. If the user asks to insert them into the SysML model, find the project and redefine the inherited logicalContext and logicalContextImpl part usages (note: multiplicity is [0..1]).";
            create_questions = (
                "Is a logical architecture required for this project?",
                "What are the key logical components or subsystems?",
                "Are there technology-independent partitioning principles to apply (e.g., separation of concerns, layers)?"
            );
            validation_prompt =
                "Validate the logicalContext against the SYSMOD Logical Architecture concept and report findings grouped as errors, warnings, and suggestions.
                Check:
                1. If present, the logicalContext part usage specializes specificationContext, and the logicalContextImpl part usage specializes logicalContext and specificationContextImpl.
                2. At least one logical component is defined as a part usage within logicalSystemImpl.
                3. Logical components are technology-independent — check for product-specific naming, vendor names, physical form factors, or deployment-specific details that belong in the productContext.
                4. Each logical component is traceable to at least one function from the functionalContext (if present) via allocation or doc comment.
                5. If a functionalContext is present in the project, a functional2logical allocation is defined connecting functionalContext to logicalContext, and a functionalImpl2logicalImpl allocation connects the white box contexts.
                6. If a productContext is present in the project, a logical2product allocation is defined connecting logicalContext to productContext, and a logicalImpl2productImpl allocation connects the white box contexts.
                7. Logical component interfaces are defined where components interact, using port and interface definitions.
                Report each finding with the element name, the violated SYSMOD rule, and a concrete suggestion for correction.";
        }

        metadata productContextAI : AI about productContext {
            doc
            /* Defines the concrete, physical or deployable product architecture that satisfies
             * the system requirements. Like the functional and logical contexts it is optional,
             * e.g., when a project ends with a logical architecture.
             *
             * When to use:
             * - The user wants to define concrete hardware/software components, physical parts,
             *   or deployment structure, or connect them via ports/interfaces.
             * - System requirements exist (and, if used, logical architecture) and the project is
             *   ready to commit to concrete building blocks.
             *
             * When not to use:
             * - The user wants technology-independent structure or behavior — use
             *   logicalContextAI or functionalContextAI instead.
             * - Product components would need to reference each other's internals directly
             *   rather than through a published port/interface — flag that as a MOSA violation
             *   rather than modeling it.
             */
            name = "sysmod-product-architecture";
            create_prompt =
                "1. Specialize specificationContext (black box view) within productContext by redefining the inherited productSystem part (the redefined black box soi) with a product-level definition.
                2. Specialize productContext and specificationContextImpl within productContextImpl (white box view) by redefining the inherited productSystemImpl part. Define product components as part usages within productSystemImpl, representing physical or deployable building blocks (hardware, software components, assemblies).
                3. If a logical architecture is present, create the logical2product allocation (black box contexts) and the logicalImpl2productImpl allocation (white box contexts) by redefining the inherited allocation usages in the project, and allocate the logical components to the product components within logicalImpl2productImpl.
                4. Include interfaces between product components where relevant.
                5. Create the SysML v2 textual notation for the productContext and the productContextImpl.
                6. If the user asks to insert them into the SysML model, find the project and redefine the inherited productContext and productContextImpl part usages.";
            create_questions = (
                "What are the main physical or deployable components of the system?",
                "Are there hardware/software splits or deployment boundaries to model?",
                "Which product components are derived from the logical architecture?"
            );
            validation_prompt =
                "Validate the productContext against the SYSMOD Product Architecture concept and report findings grouped as errors, warnings, and suggestions.
                Check:
                1. The productContext part usage is present in the project and specializes specificationContext; the productContextImpl part usage is present and specializes productContext and specificationContextImpl.
                2. At least one product component is defined as a part usage within productSystemImpl.
                3. Product components represent concrete, physical or deployable building blocks — check that logical or functional abstractions have been resolved to specific technologies, hardware types, or software components.
                4. Each product component is traceable to at least one logical component from the logicalContext (if present) via the logical2product allocation or doc comment.
                5. If a logicalContext is present in the project, a logical2product allocation is defined connecting logicalContext to productContext; if a logicalContextImpl is present, a logicalImpl2productImpl allocation connects logicalContextImpl to productContextImpl.
                6. Interfaces between product components are defined where components interact physically or through APIs.
                7. All system requirements are satisfied — verify that a satisfy relationship chain exists from the product architecture back to the systemRequirementSpecification.
                8. Every dependency between two product components crosses only through a defined port/interface — flag any part-to-part reference that bypasses the published interface. A back-door dependency is both a MOSA violation and the exact thing that breaks module-scoped context retrieval.
                9. Each component's published interface is specified completely enough that a neighbor — or an AI assistant — never needs that component's internal structure to use it correctly.
                Report each finding with the element name, the violated SYSMOD rule, and a concrete suggestion for correction.";
        }

        metadata verificationContextAI : AI about verificationContext {
            doc
            /* Specifies the verification context — the system under verification, e.g., the product
             * system, a prototype, or a simulation model, plus the test systems — and binds the
             * verification cases it holds, which were specified with the system requirements, to
             * the system under verification (step specifyVerificationContext).
             *
             * When to use:
             * - The system under verification is known and the user wants to set up the test
             *   environment (test benches, wind tunnels, simulators) as actors.
             * - The verification cases of the specification are to be bound to the system under
             *   verification and its elements, e.g., the drone under test.
             *
             * When not to use:
             * - The user wants to state what is verified and when a verification case passes —
             *   that is specified earlier against the black box; use
             *   verificationCasesAI.
             * - The system under verification is not modeled yet — model it first, e.g., with
             *   productContextAI.
             */
            name = "sysmod-verification-context";
            create_prompt =
                "1. Type the project's verificationContext, which already holds the verification cases specified in specifySystem, by a system context definition whose system of interest is the system under verification. The context can be any system context, e.g., one that specializes the productContextImpl definition and subsets the productContextImpl of the project, or a context with a prototype or a simulation model.
                2. Add the test systems needed for the verification as actors, e.g., '#externalSystem part windTunnel :> actors'.
                3. Do not create new verification case definitions or usages; if a requirement has no verification case yet, use verificationCasesAI first.
                4. Type the subject of each verification case usage by the definition of the system under verification: 'subject :>> <subject of the definition> : <system under verification definition>;'.
                5. Bind the subjects of the verified requirements that refer to internal elements to elements of the system under verification, e.g., 'requirement :>> maxReq { subject :>> deliveryDrone :> testedSystem.drones; }'.
                6. Add validation cases against the stakeholder needs, the system objectives, and the problem statement as verification case usages subsetting verificationCases.
                7. Create the SysML v2 textual notation for the verificationContext.";
            create_questions = (
                "Which test systems (test benches, simulators, test sites) are needed?",
                "What is the system under verification (product system, prototype, simulation model), and which of its elements does each verification case test?"
            );
            validation_prompt =
                "Validate the verificationContext against the SYSMOD verification concept and report findings grouped as errors, warnings, and suggestions.
                Check:
                1. The verificationContext part usage is present in the project and has the system under verification as system of interest.
                2. The test systems are actors of the verificationContext.
                3. Each verification case usage of the verificationContext subsets verificationCases and is typed by a verification case definition of the specification (no definitions created anew in the verification context).
                4. The subject of each verification case usage is typed by the definition of the system under verification.
                5. The subjects of the verified requirements are bound to elements of the system under verification where the verification case definition leaves them open.
                Report each finding with the element name, the violated SYSMOD rule, and a concrete suggestion for correction.";
        }

        metadata tradeStudiesAI : AI about tradeStudies {
            doc
            /* Evaluates alternative architectures for an architecture decision with a SYSMOD trade study
             * (SYSMODTradeStudy) against the system objectives, selects one, and records the decision.
             *
             * When to use:
             * - An architecture decision has two or more viable alternatives, e.g., candidate system ideas,
             *   logical decompositions, or product architectures, and the project needs a traceable choice.
             * - The user asks to compare alternatives, to run a trade-off analysis, or to justify why an
             *   architecture was selected.
             *
             * When not to use:
             * - There is only one viable alternative, or the decision is fixed by the brownfield system —
             *   record a short Rationale on the context instead of a trade study.
             * - The user wants to define the selected architecture itself — use the AI metadata of that
             *   context (e.g. productContextAI) after the trade study.
             */
            name = "sysmod-trade-studies";
            create_prompt =
                "1. Identify the architecture decision and the project context it is about (e.g. productContextImpl for a product architecture, systemIdeaContextImpl for a system idea).
                2. Exclude alternatives that violate a mandatory requirement of the systemRequirementSpecification, if it already exists, and tell the user which ones and why.
                3. Make the project context of the decision a variation usage (e.g. variation part :>> productContextImpl :> <base context usages> { ... }). For each remaining alternative, create a #systemContext part definition that specializes the definition of the base context of the decision (e.g. the definition of the white box specification context for product architecture alternatives) and a variant usage typed by it inside the variation (variant part <alternative> : <context definition>), each with a doc comment describing the alternative. For each variant, add a reference feature to the project (ref part <name> : <context definition> = <variation>::<variant>), because an analysis cannot reference variants directly.
                4. Create an analysis usage typed by SYSMODTradeStudy subsetting tradeStudies, with a doc comment stating the decision question. Bind its subject alternatives to the reference features of the variants and its criteria to the relevant system objectives (concern usages nested in systemObjectives).
                5. Create one assessment per alternative and criterion as an attribute usage subsetting assessments that refers to the alternative and the criterion and sets the score from 0.0 (objective not achieved) to 1.0 (objective fully achieved). Keep the default weight, i.e., the priority of the objective, unless the user gives another weight. Ask for the evidence of each score (analysis, simulation, or expert judgment) and document it in a doc comment.
                6. Compute the evaluation of each alternative (the sum of weight times score over its assessments) and name the selected alternative, i.e., the one with the maximum evaluation. Report ties or close results to the user instead of deciding silently.
                7. Bind the variation to the selected variant (variation part :>> <project context> :> <base context usages> = <variation>::<selected variant> { ... }), so that the project context resolves to the selected alternative. Annotate the variation with ModelingMetadata::Rationale, whose text names the selected variant and summarizes the decision, and whose explanation refers to the trade study (explanation = <project>::<trade study> meta SysML::Usage).
                8. Create the SysML v2 textual notation for the variation with its variants, the trade study, and the Rationale.";
            create_questions = (
                "Which architecture decision should be evaluated, and which project context does it concern?",
                "Which alternatives are considered?",
                "Which system objectives are the criteria, and should any weight differ from the priority of the objective?",
                "How well does each alternative achieve each objective (0.0 to 1.0), and what is the evidence?"
            );
            validation_prompt =
                "Validate the tradeStudies against the SYSMOD trade study concept and report findings grouped as errors, warnings, and suggestions.
                Check:
                1. Each trade study is an analysis usage typed by SYSMODTradeStudy (or a specialization) and subsets tradeStudies.
                2. The subject alternatives is bound to at least two reference features that refer to variants of the same variation usage (a project context), typed by #systemContext part definitions specializing the same base context definition.
                3. The criteria are bound to concern usages of systemObjectives; each criterion has a priority, or each of its assessments sets an explicit weight.
                4. There is exactly one assessment per alternative and criterion; each score lies between 0.0 and 1.0 and has documented evidence.
                5. No alternative violates a mandatory requirement of the systemRequirementSpecification.
                6. The variation is bound to the variant with the maximum evaluation and carries Rationale metadata whose explanation refers to the trade study and whose text names that variant as the selected one.
                7. If the evaluations of the best alternatives differ only slightly, a sensitivity remark is documented, e.g., which change of weights or scores would change the selection.
                Report each finding with the element name, the violated SYSMOD rule, and a concrete suggestion for correction.";
        }

        metadata subProjectsAI : AI about subProjects {
            doc
            /* Decomposes a project into sub-projects for building blocks that are developed separately,
             * sets up the sub-project contract (handover package with handover context, stakeholders, and requirements; requirement
             * flow-down), and integrates the designs of the sub-projects into the parent architecture.
             *
             * When to use:
             * - The user wants to split a large project into subsystem- or component-level projects, e.g.,
             *   for another team or a supplier, or asks how a subsystem/component should be organized as
             *   its own project.
             * - The product architecture of the parent project is at least roughly defined, and some of
             *   its building blocks need their own project context (modelSubProjects).
             * - The product architectures of the sub-projects are available and must be integrated into
             *   the parent architecture (integrateSubProjects).
             *
             * When not to use:
             * - The project is small enough to stay a single, non-decomposed project — do not create
             *   sub-projects speculatively.
             * - The user works inside an existing sub-project and wants to derive its element
             *   specification from the parent — use handoverAI in the sub-project.
             * - The user wants to define an artifact within the current project's own scope — use that
             *   artifact's own AI metadata instead of creating a sub-project.
             */
            name = "sysmod-sub-projects";
            create_prompt =
                "1. Identify the building blocks of the white box product context (productContextImpl) that are developed separately. Each must be typed by a black box part definition whose ports describe its interfaces.
                2. For each of them, create an occurrence definition specializing Project (or a #project occurrence def) for the sub-project, with its own projectOwner and problemStatement.
                3. Add each sub-project as an occurrence usage subsetting subProjects within the parent project.
                4. For each building block, create a handover package with a handover context: a #systemContext part definition specializing SystemContext whose system of interest redefines soi and is typed by a black box part definition of the building block; an actor (subsetting actors, typed by a part definition with only the ports that face the building block, ports subsetting actorPorts, tagged #user, #externalSystem, or #environmentalEffect) for each neighbor of the building block in the white box and for each parent actor whose interface the parent delegates to it; and an actor/system interface (subsetting asis) for each connection and delegation. Hand over only what the sub-project needs, not the internal structure of the neighbors. The handover package must not import the parent architecture, so that a sub-project without access to the parent model, e.g., a supplier, can use it. The handover package also contains the parent stakeholders that the sub-project needs (stakeholder definitions that the parent's stakeholder definitions specialize) and the handover requirements: a requirement definition with the system of interest definition of the handover context as subject, containing the requirements that the parent imposes on the building block.
                5. Let the white box product context specialize the elements of the handover context: the building block is typed by the system of interest definition, and the neighbors are additionally typed by the actor definitions, with their ports redefining the handed-over ports.
                6. In each sub-project, apply handoverAI to take over the handover context as its brownfield context and to derive its system requirements.
                7. Declare the requirement flow-down in the parent project: one #derivation connection subsetting requirementFlowDowns per parent requirement that constrains the building block, with end #original ::> <parent requirement> and one end #derive ::> <sub-project usage>.handoverRequirements.<handover requirement> per handover requirement (private import RequirementDerivation::*). If the parent model does not contain the definition of the sub-project, e.g., for a supplier, type the sub-project usage by Project and redefine handoverRequirements in it with the handover requirement definition. The parent project declares the flow-down because only there the requirements of both levels are accessible.
                8. Hand over shared stakeholders via the handover package (step 4); the sub-project does not reference the parent project's elements.
                9. Integration (integrateSubProjects): when the product architecture of a sub-project is available, bind the building block in the parent's productContextImpl usage to the white box product system of the sub-project, e.g. part :>> <building block> = <sub-project usage>.<productContextImpl usage>.<system>. If the sub-project delivers only a black box, e.g., a supplier, keep the type of the handover context and document the delivery with the verification results.
                10. Create the SysML v2 textual notation for the sub-project definitions, their usages, the handover packages, the requirementFlowDowns, and the integration redefinitions.
                11. If the user asks to insert sub-projects into the SysML model, find the parent project and add the sub-project occurrence usages.";
            create_questions = (
                "Which building blocks of the product architecture are developed in sub-projects?",
                "Who owns each sub-project (team or supplier)?",
                "Do the sub-projects share stakeholders with the parent project?",
                "Are the product architectures of the sub-projects available for integration?"
            );
            validation_prompt =
                "Validate the subProjects against the SYSMOD sub-project concept and report findings grouped as errors, warnings, and suggestions.
                Check:
                1. Each sub-project occurrence usage subsets the inherited subProjects and is typed by an occurrence definition specializing Project or AIProject.
                2. Each sub-project develops a building block of the parent's productContextImpl, and the building block is typed by the system of interest definition of the sub-project's handover context.
                3. Each sub-project has a projectOwner, a problemStatement that is consistent with and narrower in scope than the parent project's problemStatement, and a brownfieldContext typed by its handover context (see the validation_prompt of handoverAI).
                4. Each handover context covers every neighbor of the building block in the parent white box and every parent actor delegated to it, with an actor/system interface per connection and delegation; the parent white box specializes its elements; and its handover package does not import the parent architecture.
                5. The parent project has requirementFlowDowns whose #original ends are its own requirements and whose #derive ends are handoverRequirements of the sub-projects, reached via the sub-project usages; every parent requirement that constrains the building block of a sub-project is the original of at least one flow-down, or a doc comment explains why it does not flow down.
                6. Stakeholders shared with a sub-project are defined in its handover package and specialized by the parent's stakeholder definitions, rather than referenced from the sub-project or duplicated as independent definitions.
                7. There are no overlapping scopes between sibling sub-projects — each sub-project develops a distinct building block.
                8. After integration, the parent's productContextImpl binds each building block to the white box product system of its sub-project, whose definition specializes the system of interest definition of the handover context, or the building block stays a black box with documented verification results.
                9. Each sub-project has a meaningful name and doc comment describing its scope and relationship to the parent project.
                Report each finding with the element name, the violated SYSMOD rule, and a concrete suggestion for correction.";
        }

        metadata handoverAI : AI about handoverRequirements {
            doc
            /* Sets up the element specification of a sub-project from its parent project (sub-project
             * contract): the handover context of the parent as the brownfield context, and the system
             * requirements derived from the handover requirements of the parent.
             *
             * When to use:
             * - A sub-project has been created for a building block of the parent's product architecture
             *   and needs its starting point: the system boundary, the actors, the interfaces, and the
             *   requirements that the parent imposes.
             * - The parent architecture or the parent requirements changed, and the sub-project must check
             *   the impact on its brownfield context and its requirements.
             *
             * When not to use:
             * - The project is a top-level project without a parent — use brownfieldContextAI and
             *   systemRequirementSpecificationAI directly.
             * - The user wants to decompose a project into sub-projects or to integrate their results —
             *   use subProjectsAI in the parent project.
             */
            name = "sysmod-sub-project-contract";
            create_prompt =
                "1. Find the handover package that the parent project provides for this sub-project. The sub-project uses only this package from the parent project.
                2. Use the handover context as the black box brownfield context of the sub-project (part <name> :>> brownfieldContext : <handover package>::<handover context>). Do not use any other element of the parent architecture: the sub-project, e.g., a supplier, may have no access to it.
                3. If the sub-project needs an actor or interface that the handover context lacks, report it as a request to the parent project instead of adding it in the sub-project.
                4. Put the internal structure of an existing implementation of the element, if any, into the white box brownfield context; its definition specializes the system of interest definition of the handover context.
                5. Redefine handoverRequirements with the handover requirement definition of the handover package (requirement :>> handoverRequirements : <handover package>::<handover requirement definition>), and use the handover stakeholders as the stakeholders of the sub-project.
                6. Derive the system requirements of the sub-project from the handover requirements in its systemRequirementSpecification, with the system of interest definition of the handover context as subject and a motivation that explains the derivation. Declare the derivation in the sub-project: one #derivation connection per handover requirement, with end #original ::> handoverRequirements.<handover requirement> and one end #derive ::> <requirement specification usage>.<requirement> per derived requirement (private import RequirementDerivation::*).
                7. If a requirement that the sub-project needs is missing from the handover requirements, report it as a request to the parent project instead of adding it as a handover requirement.
                8. Create the SysML v2 textual notation for the handoverRequirements redefinition, the brownfield contexts, the derived requirements, and their #derivation connections.";
            create_questions = (
                "Which project is the parent, and which building block does this sub-project develop?",
                "Does an implementation of the building block already exist (brownfield)?",
                "Which parent requirements constrain the building block?"
            );
            validation_prompt =
                "Validate the sub-project contract and report findings grouped as errors, warnings, and suggestions.
                Check:
                1. The sub-project imports no package of the parent project other than its handover package.
                2. The brownfieldContext is typed by the handover context of the parent project or a specialization of it.
                3. The sub-project uses no element of the parent architecture other than the handover package (shared definitions such as stakeholders or domain items are allowed).
                4. If the sub-project has access to the parent model: each actor of the handover context corresponds to a neighbor of the building block in the parent white box or to a parent actor delegated to it, each actor/system interface to a connection or delegation, and the parent white box specializes them.
                5. handoverRequirements is typed by the handover requirement definition of the handover package, and each handover requirement is the #original of a #derivation connection in the sub-project, or a doc comment explains why it is not refined.
                6. Every system requirement of the sub-project is either the #derive end of such a #derivation connection or frames a stakeholder need of the sub-project.
                7. The derived requirements are consistent with the handover requirements, i.e., they do not relax them, and their subject is the system of interest definition of the handover context.
                Report each finding with the element name, the violated SYSMOD rule, and a concrete suggestion for correction.";
        }
    }
}
